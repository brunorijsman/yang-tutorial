module stove {

    namespace "http://remoteautonomy.com/yang-schemas/stove";
    prefix stove;

    organization
      "Remote Autonomy";

    contact
      "Bruno Rijsman
       brunorijsman@remoteautonomy.com";

    description
      "This module contains a collection of YANG definitions for managing a stove.";

    revision 2022-03-12 {
        description
          "Initial revision.";
    }

    container burners {
        description
          "The burners of the stove.";

        list burner {
            key "location";
            description
              "The list of burners on the stove.";

            leaf location {
                type enumeration {
                    enum bottom-left;
                    enum bottom-right;
                    enum top-left;
                    enum top-right;
                }
                description
                  "The location of the burner on the stove top.";
            }

            leaf temperature-setting {
                type int8 {
                    range "0..10";
                }
                mandatory true;
                description
                  "The temperature setting for the burrner. 0 is off. 1 through 10 are temperature
                   settings from low to high.";
            }

            leaf actual-temperature-in-celcius {
                type int16;
                config false;
                description
                  "The actual temperature in degrees Celcius.";
            }
        }
    }
}
